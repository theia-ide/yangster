module example-3-a {

  yang-version "1.1";

  namespace "http://example.com/example-3/a";

  prefix "ex3a";

  
  include example-3-suba {
    revision-date 2016-07-21;
  }
  revision 2016-06-18;

  feature fea1;

  feature fea2;

  identity idX;

  grouping gbar {
    leaf bar {
      type string;
    }
  }

  container top {
    leaf foo {
      if-feature "fea1";
      type empty;
    }
  }

}
