module xyt6 {
    namespace 'ff';
    prefix 'sss';

    choice XXXXXXDDDDDDDDDDDDXX {
        default: 'x';
        leaf 'bar' {
            type string;
        }
        leaf 'bar1' {
            type string;
        }
        leaf 'SSSSSSSSSSSSSSSDDS' {
            type string;
        }

    }
}
