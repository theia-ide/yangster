submodule example-3-suba {

  yang-version "1.1";

  belongs-to example-3-a {
    prefix "ex3a";
  }

  revision 2016-07-21;

  /*
  augment "/ex3a:top" {
    uses gbar;
    leaf baz {
      if-feature "fea2";
      type inet:ipv4-address-no-zone;
    }
  }
  */
}
